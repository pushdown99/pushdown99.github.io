module samsung-5g {
  namespace "http://www.samsung.com/ns/samsung-5g";
  prefix samsung-5g;

  container management-element {
    leaf ne-id {
      type  uint32{
             range "0 .. 100";
         }
    }
  }
}
